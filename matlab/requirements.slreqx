# requirements

## #1: Stop button (Functional)
When the vehicle is driving automatically the control panel shall provide the technician with the ability to stop the vehicle in a controlled manner with a button.

### #5: Stop button malfunction (Functional)
When the stop button malfunctions the vehicle shall execute controlled stop with shutdown

## #4: Execution of controlled stop (Functional)
When the controlled stop is initiated the truck shall use the braking torque of its driving unit to stop itself.

### #2: Emergency stop for low deceleration (Functional)
When the controlled stop doesn't achieve the described deceleration level the vehicle shall initiate emergency stop.

### #3: Deceleration level for controlled stop (Functional)
The controlled stop shall achieve -10 m/s2 deceleration.

## #6: Controlled stop with shutdown (Functional)
When the vehicle executed a controlled stop with shutdown, the power of its driving unit shall shutdown.

### #7: Deceleration level for controlled stop (Functional)
The controlled stop with shutdown shall achieve -10 m/s2 deceleration.
